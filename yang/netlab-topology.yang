module netlab-topology {
  yang-version 1.1;
  namespace "urn:exergy-connect:netlab:topology";
  prefix nt;

  import netlab-types {
    prefix ntype;
  }

  organization "Exergy Connect";
  description
    "Public Netlab topology root. Runtime uses unprefixed JSON members matching
     this module's data nodes (xYang hybrid encoding).

     Schema coverage mirrors Netlab defaults/attributes.yml for core topology
     objects; transform-control lists (link_no_propagate, pool_no_copy, …)
     stay in YAML and are applied by the JS pipeline.";

  revision 2026-07-16 {
    description
      "Factor shared interface/neighbor/addressing leaves into groupings.";
  }

  grouping mtu {
    leaf mtu {
      type uint16 {
        range "64..9216";
      }
    }
  }

  grouping ipv4-ipv6 {
    description "Address leaves typed as Netlab prefixes (or boolean unnumbered).";
    leaf ipv4 {
      type ntype:ipv4-prefix;
    }
    leaf ipv6 {
      type ntype:ipv6-prefix;
    }
  }

  grouping neighbor-body {
    description "Neighbor ifname and addresses (key leaf node supplied by caller).";
    leaf ifname {
      type string;
    }
    uses ipv4-ipv6;
  }

  grouping neighbor {
    description "Neighbor attachment with a string node key.";
    leaf node {
      type string;
    }
    uses neighbor-body;
  }

  grouping if-identity {
    description "Interface index and name.";
    leaf ifindex {
      type uint32;
    }
    leaf ifname {
      type string;
    }
  }

  container topology {
    leaf stage {
      type ntype:stage-name;
      description "Set by the orchestrator immediately before each validate() call.";
    }

    leaf name {
      type string;
    }

    leaf provider {
      type ntype:provider-name;
      default clab;
    }

    leaf-list module {
      type string;
    }

    container defaults {
      leaf device {
        type ntype:device-name;
      }
    }

    list nodes {
      key "name";
      leaf name {
        type ntype:node-id-ref;
      }
      leaf device {
        type ntype:device-name;
      }
      leaf provider {
        type ntype:provider-name;
        description "Per-node provider override (e.g. from groups).";
      }
      leaf id {
        type uint32 {
          range "1..150";
        }
      }
      leaf role {
        type ntype:node-role;
      }
      leaf-list module {
        type string;
      }
      leaf box {
        type string;
      }
      leaf router_id {
        type string;
        description "IPv4 router id (attributes.yml use: id).";
      }
      uses mtu;
      leaf unmanaged {
        type boolean;
      }
      leaf memory {
        type uint32;
      }
      leaf cpu {
        type string;
      }
      leaf-list skip_config {
        type string;
      }
      leaf-list group {
        type string;
      }
      anydata config {
        description "Inline config templates (list or dict; files plugin).";
      }
      leaf _daemon {
        type boolean;
      }
      leaf _daemon_parent {
        type string;
      }
      container mgmt {
        leaf ipv4 {
          type string;
        }
        leaf ipv6 {
          type string;
        }
        leaf mac {
          type string;
        }
        leaf ifname {
          type string;
        }
      }
      container loopback {
        uses if-identity;
        leaf type {
          type string;
        }
        uses ipv4-ipv6;
        leaf pool {
          type string;
        }
        leaf virtual_interface {
          type boolean;
        }
        list neighbors {
          key "node";
          uses neighbor;
        }
      }
      uses ntype:af-flags;
      list interfaces {
        key "ifindex";
        uses if-identity;
        uses ipv4-ipv6;
        leaf linkindex {
          type uint32;
        }
        leaf type {
          type string;
        }
        leaf role {
          type string;
        }
        leaf pool {
          type string;
          description "Address pool name copied from the parent link.";
        }
        leaf bridge {
          type string;
        }
        leaf name {
          type string;
        }
        uses mtu;
        leaf vrf {
          type string;
        }
        leaf virtual_interface {
          type boolean;
        }
        list neighbors {
          key "node";
          leaf node {
            type leafref {
              path "/topology/nodes/name";
            }
          }
          uses neighbor-body;
        }
      }
      must "/topology/stage = 'user_input' or /topology/stage = 'normalized' or id" {
        error-message "node id is required from addressed stage onward";
        error-app-tag "MISSING";
      }
    }

    list links {
      key "linkindex";
      leaf linkindex {
        type uint32;
      }
      leaf _linkname {
        type string;
        description
          "Internal diagnostic name. Runtime stores netlab-internal:_linkname;
           the validate adapter maps that qualified member onto this leaf.";
      }
      must "/topology/stage = 'user_input' or _linkname" {
        error-message "netlab-internal:_linkname is required after user_input stage";
        error-app-tag "MISSING";
      }
      leaf type {
        type ntype:link-type;
      }
      leaf bridge {
        type string;
      }
      leaf name {
        type string;
      }
      leaf role {
        type string;
      }
      leaf pool {
        type string;
      }
      leaf node_count {
        type uint32;
        description "Number of attachment points on the link (set during transform).";
      }
      leaf disable {
        type boolean;
      }
      leaf shutdown {
        type boolean;
      }
      leaf unnumbered {
        type boolean;
      }
      leaf vlan_name {
        type string;
      }
      leaf parentindex {
        type uint32;
      }
      leaf bandwidth {
        type uint64;
      }
      uses mtu;
      container prefix {
        uses ipv4-ipv6;
        leaf allocation {
          type ntype:allocation-mode;
        }
      }
      list interfaces {
        key "node";
        leaf node {
          type leafref {
            path "/topology/nodes/name";
          }
        }
        uses ipv4-ipv6;
        uses if-identity;
      }
      must "/topology/stage = 'user_input' or linkindex" {
        error-message "linkindex is required after user_input stage";
        error-app-tag "MISSING";
      }
    }

    container addressing {
      list pool {
        key "name";
        leaf name {
          type string;
        }
        uses ipv4-ipv6;
        leaf prefix {
          type uint8 {
            range "1..32";
          }
        }
        leaf prefix6 {
          type uint8 {
            range "1..128";
          }
        }
        leaf start {
          type uint32;
        }
        leaf allocation {
          type ntype:allocation-mode;
        }
        leaf mac {
          type string;
        }
        leaf unnumbered {
          type boolean;
        }
      }
    }

    list groups {
      key "name";
      leaf name {
        type string;
      }
      leaf-list members {
        type string;
      }
      leaf device {
        type ntype:device-name;
      }
      leaf provider {
        type ntype:provider-name;
      }
      leaf-list module {
        type string;
      }
      leaf-list config {
        type string;
      }
      anydata vars {
        description "Group Ansible vars.";
      }
      anydata node_data {
        description "Data copied onto group member nodes.";
      }
      leaf _auto_create {
        type boolean;
      }
    }
  }
}
