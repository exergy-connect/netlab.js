module netlab-vlan {
  yang-version 1.1;
  namespace "urn:exergy-connect:netlab:vlan";
  prefix vlan;

  import netlab-topology {
    prefix nt;
  }

  organization "Exergy Connect";
  description "VLAN module augmentations.";

  revision 2026-07-16 {
    description
      "vlan-definition grouping for global/node VLAN lists; keep vlan-if-attrs.";
  }

  grouping vlan-if-attrs {
    description "VLAN attributes on a physical or SVI interface.";
    leaf access {
      type string;
    }
    leaf-list trunk {
      type string;
    }
    leaf native {
      type string;
    }
    leaf mode {
      type string;
    }
    leaf name {
      type string;
      description "VLAN name on SVI interfaces.";
    }
    leaf access_id {
      type uint16 {
        range "1..4094";
      }
    }
  }

  grouping vlan-definition {
    description "Shared VLAN object fields (global and per-node).";
    leaf name {
      type string;
    }
    leaf id {
      type uint16 {
        range "1..4094";
      }
    }
    leaf mode {
      type string;
    }
    leaf bridge_group {
      type uint32;
    }
    container prefix {
      leaf ipv4 { type string; }
      leaf ipv6 { type string; }
    }
  }

  augment "/nt:topology" {
    list vlans {
      key "name";
      uses vlan-definition;
      leaf-list links {
        type string;
        description "Access-link shorthand (e.g. dut-h1).";
      }
    }
  }

  augment "/nt:topology/nt:nodes" {
    container vlan {
      description "Node-level VLAN module state (e.g. max_bridge_group).";
      leaf mode {
        type string;
      }
      leaf max_bridge_group {
        type uint32;
      }
    }
    list vlans {
      key "name";
      uses vlan-definition;
    }
  }

  augment "/nt:topology/nt:links" {
    container vlan {
      uses vlan-if-attrs;
    }
  }

  augment "/nt:topology/nt:links/nt:interfaces" {
    container vlan {
      uses vlan-if-attrs;
    }
  }

  augment "/nt:topology/nt:nodes/nt:interfaces" {
    leaf mode {
      type string;
      description "Copied onto SVI from VLAN data during transform.";
    }
    leaf bridge_group {
      type uint32;
      description "Copied onto SVI from VLAN data during transform.";
    }
    container vlan {
      uses vlan-if-attrs;
    }
  }

  augment "/nt:topology/nt:nodes/nt:interfaces/nt:neighbors" {
    container vlan {
      uses vlan-if-attrs;
    }
  }
}
