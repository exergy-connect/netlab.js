module netlab-bgp {
  yang-version 1.1;
  namespace "urn:exergy-connect:netlab:bgp";
  prefix bgp;

  import netlab-topology {
    prefix nt;
  }

  organization "Exergy Connect";
  description "BGP module augmentations.";

  revision 2026-07-16 {
    description "bgp-rr-attrs grouping for group/node BGP containers.";
  }

  grouping bgp-rr-attrs {
    description "BGP AS and route-reflector attributes shared by groups and nodes.";
    leaf as {
      type uint32;
    }
    leaf rr {
      type boolean;
    }
    leaf rr_cluster_id {
      type string;
    }
    leaf rr_mesh {
      type boolean;
    }
  }

  augment "/nt:topology" {
    container bgp {
      leaf as {
        type uint32;
      }
    }
  }

  // Groups inherit the node attribute namespace (attributes.yml node_group).
  augment "/nt:topology/nt:groups" {
    container bgp {
      uses bgp-rr-attrs;
    }
  }

  augment "/nt:topology/nt:nodes" {
    container bgp {
      uses bgp-rr-attrs;
      leaf router_id {
        type string;
      }
      list neighbor {
        key "name";
        leaf name {
          type string;
        }
        leaf as {
          type uint32;
        }
        leaf type {
          type string;
        }
        leaf ipv4 {
          type string;
        }
        leaf ipv6 {
          type string;
        }
        leaf evpn {
          type string;
          description "EVPN address-family activation (e.g. ipv4).";
        }
      }
    }
  }

  augment "/nt:topology/nt:nodes/nt:interfaces" {
    container bgp {
      leaf local_as {
        type uint32;
      }
      leaf replace_global_as {
        type boolean;
      }
      leaf advertise {
        type boolean;
      }
    }
  }

  augment "/nt:topology/nt:links" {
    container bgp {
      leaf advertise {
        type boolean;
      }
    }
  }
}
