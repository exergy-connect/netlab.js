module netlab-isis {
  yang-version 1.1;
  namespace "urn:exergy-connect:netlab:isis";
  prefix isis;

  import netlab-topology {
    prefix nt;
  }

  organization "Exergy Connect";
  description "IS-IS module augmentations.";

  revision 2026-07-16 {
    description "isis-common grouping for topology/node IS-IS containers.";
  }

  grouping isis-common {
    description "IS-IS attributes shared by topology and node containers.";
    leaf area {
      type string;
    }
    leaf type {
      type string;
    }
  }

  augment "/nt:topology" {
    container isis {
      uses isis-common;
    }
  }

  augment "/nt:topology/nt:nodes" {
    container isis {
      uses isis-common;
      leaf net {
        type string;
      }
    }
  }

  augment "/nt:topology/nt:nodes/nt:interfaces" {
    container isis {
      leaf network_type {
        type string;
      }
      leaf metric {
        type uint32;
      }
      leaf passive {
        type boolean;
      }
    }
  }
}
