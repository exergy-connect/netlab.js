module netlab-evpn {
  yang-version 1.1;
  namespace "urn:exergy-connect:netlab:evpn";
  prefix evpn;

  import netlab-topology {
    prefix nt;
  }

  organization "Exergy Connect";
  description "EVPN module augmentations.";

  revision 2026-07-16 {
    description "evpn-common and evpn-rt-attrs groupings.";
  }

  grouping evpn-common {
    description "EVPN attributes shared by topology and node containers.";
    leaf-list session { type string; }
    leaf transport { type string; }
    leaf-list vlans { type string; }
    leaf-list vrfs { type string; }
  }

  grouping evpn-rt-attrs {
    description "EVPN route-target / EVI attributes on VLAN objects.";
    leaf evi { type uint32; }
    leaf rd { type string; }
    leaf-list import { type string; }
    leaf-list export { type string; }
  }

  augment "/nt:topology" {
    container evpn {
      uses evpn-common;
      leaf as { type uint32; }
    }
  }

  augment "/nt:topology/nt:nodes" {
    container evpn {
      uses evpn-common;
      leaf domain { type string; }
    }
  }

  augment "/nt:topology/nt:vlans" {
    container evpn {
      uses evpn-rt-attrs;
    }
  }

  augment "/nt:topology/nt:nodes/nt:vlans" {
    container evpn {
      uses evpn-rt-attrs;
    }
  }
}
