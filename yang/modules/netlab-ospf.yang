module netlab-ospf {
  yang-version 1.1;
  namespace "urn:exergy-connect:netlab:ospf";
  prefix ospf;

  import netlab-topology {
    prefix nt;
  }
  import netlab-types {
    prefix ntype;
  }

  organization "Exergy Connect";
  description "OSPF module augmentations.";

  revision 2026-07-16 {
    description
      "ospf-link-attrs grouping; reuse ntype:af-flags (requires xYang ≥ 0.1.6).";
  }

  grouping ospf-link-attrs {
    description "OSPF attributes common to interfaces and links.";
    leaf area {
      type string;
    }
    leaf network_type {
      type string;
    }
    leaf cost {
      type uint32;
    }
  }

  augment "/nt:topology" {
    container ospf {
      leaf area {
        type string;
      }
    }
  }

  augment "/nt:topology/nt:nodes" {
    container ospf {
      leaf area {
        type string;
      }
      leaf router_id {
        type string;
      }
      leaf passive {
        type boolean;
      }
      uses ntype:af-flags;
    }
  }

  augment "/nt:topology/nt:nodes/nt:interfaces" {
    container ospf {
      uses ospf-link-attrs;
      leaf passive {
        type boolean;
      }
    }
  }

  augment "/nt:topology/nt:links" {
    container ospf {
      uses ospf-link-attrs;
    }
  }
}
