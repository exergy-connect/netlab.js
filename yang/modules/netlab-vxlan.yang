module netlab-vxlan {
  yang-version 1.1;
  namespace "urn:exergy-connect:netlab:vxlan";
  prefix vxlan;

  import netlab-topology {
    prefix nt;
  }

  organization "Exergy Connect";
  description "VXLAN module augmentations.";

  revision 2026-07-16 {
    description "vxlan-common and vxlan-vlan-attrs groupings.";
  }

  grouping vxlan-common {
    description "VXLAN attributes shared by topology and node containers.";
    leaf domain { type string; }
    leaf flooding { type string; }
    leaf-list vlans { type string; }
  }

  grouping vxlan-vlan-attrs {
    description "VXLAN attributes attached to VLAN objects.";
    leaf vni {
      type uint32 {
        range "1..16777215";
      }
    }
    leaf-list vtep_list { type string; }
  }

  augment "/nt:topology" {
    container vxlan {
      uses vxlan-common;
      leaf use_v6_vtep { type boolean; }
    }
  }

  augment "/nt:topology/nt:nodes" {
    container vxlan {
      uses vxlan-common;
      leaf vtep { type string; }
      leaf vtep_interface { type string; }
      leaf transport { type string; }
      leaf-list vtep_list { type string; }
      leaf-list l3vnis { type string; }
    }
  }

  augment "/nt:topology/nt:vlans" {
    uses vxlan-vlan-attrs;
  }

  augment "/nt:topology/nt:nodes/nt:vlans" {
    uses vxlan-vlan-attrs;
  }
}
